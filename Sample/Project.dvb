Attribute VB_Name = "ThisDrawing"
Attribute VB_Base = "0{8E75D913-3D21-11D2-85C4-080009A0C626}"
Attribute VB_GlobalNameSpace = False
Attribute VB_Creatable = False
Attribute VB_PredeclaredId = True
Attribute VB_Exposed = True
Attribute VB_TemplateDerived = False
Attribute VB_Customizable = True
Public Sub ff()

    Dim returnObj As AcadObject
    Dim basePnt As Variant
    ThisDrawing.Utility.GetEntity returnObj, basePnt, "Select an object"
    
    Dim a As AsdkDeepPropInspectorLib.AcadPie
    Set a = returnObj
    
    a.Title = "test"
    
    Dim b As AsdkDeepPropInspectorLib.AcadPieSector
    For Each b In a.Sectors
        b.Exploded = True
    Next

End Sub
